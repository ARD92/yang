/*
Yang model definition for specification IEEE 1914.3 Radio over Ethernet (WIP)
Hierarchy follows the below 
Ethernet < --- CPRI < -- Mapper Demapper < -- RoE container (structure aware)
                                ^
                                |------------ Structure agnostic

To DO:
1. Use augmentation to bring in the ethernet header for CPRI encap (IP/MPLS) 
2. How to handle plain I/Q mode which is native CPRI
3. Std sets the limit of mappers/demappers to 255. is there a limit on CPRI ports ?
4. flowID should match
*/


module radio-over-ethernet {
  prefix "roe";
  //namespace "urn:ietf:params:xml:ns:yang:roe"; 
  namespace "http://roe";

  import ietf-yang-types {
    prefix "ietf-yang-types";
  }

  import ietf-inet-types {
    prefix "ietf-inet-types";
  }

  organization "IEEE 1914.3 TF";
  revision "2020-03-19" {
    description "V1.0";
    reference "IEEE 1914.3 TF";
  }


  //type definitions
  typedef cpri-id {
  description "Unique identifier for each CPRI port";
  type uint16;
  }

  typedef sequence-id {
  description "Sequence number for packet stream";
  type uint32;
  }

  typedef speed {
    units "Mbps";
    type decimal64 {
      fraction-digits 2;
      //range "0 .. max";  
       /* Need to fill speeds applicable to CPRI.
         only 2 decimal points would be displayed. 
      */
     }
   }

  typedef mapper {
    type uint8;
        description "Unique mapper identifier";
  }


  //grouping starts   
  /************************** Not used the below ROE header **************************/
  /* Grouping for defining RoE header. 
     Reference Section 5.5.1
  // This header info is already present under mapper-demapper except for subtype. Hence not 
  // used. It seems more like this info would be copied during the underlying execution. 
  grouping roe-header {
    leaf subType {
      type uint8 ;
      description "Used to define the ROE subtype and type of
      of flow carried by the ROE packets.";
      reference  "IEEE 1914.3 Section 5.5.2 Table 3";
      }

    leaf flow-id {
      type uint8;
      description " Specifies the flow between two end points. The end points
      are defined as an SA/DA pair.";
      reference " IEEE 1914.3 Section 5.5.3 Table 4";
      config false;
      }

    leaf length {
      type uint16;
      description "Indicates the amount of data in the payload. The same as length
      when defined in an IPV6 header(16 bits).";
      reference "IEEE 1914.3 Section 5.5.4" ; 
      }

    container orderInfo {
      uses sequence-number {
      }
      uses timestamp {
      }
    }
  }
  /********************************************************************************/

  /* Grouping for sequence-number container and timestamps leaf
     Section 5.5.5.2 Table 5
  */
  grouping sequence-number {
    container sequence-number {
      description "Generic configuration values for sequence numbers";
      reference "IEEE 1914.3 Table 5";
      
	  leaf p-max {
	    type roe:sequence-id;
	    default 2147483647; // (2^31)-1 max 32 bit value
	    description
	      "Maximum numerical value of the p-counter field so
           that p-max is less than 2^32 – p-counter.";
	    reference "IEEE1914 Table 5: seqNumPMax";
	    }

	  leaf p-counter {
	    type roe:sequence-id;
	    default 0;
	    description
                  "The counter value of the p-counter field. When
                   the p-counter > p-max, then the counter
                   field wraps to a value p-counter modulo
                   (p-max + 1). The counter wrap also causes
                   q-counter to be incremented by q-increment/fixed,
                   based on the setting of q-increment/no-increment";
	    reference "IEEE1914 Table 5: seqNumPVal";
	    }

	  container p-increment {
	    reference "IEEE1914 Table 5: seqNumPIncProp";
	    leaf no-increment {
	      must "not(../fixed)";
	      type boolean;
	      default false;
	      description "No increment for p-counter value";
	    }
	    leaf fixed {
	      type roe:sequence-id;
	      default 1;
	      must "not(../no-increment)";
	      description
	  	"Increment the p-counter by a fixed value on every
                       packet sent.";
	      reference seqNumPInc;
	    }
	  }

	  leaf q-max {
	    type roe:sequence-id;
	    default 0;
	    description
	      "Maximum numerical value of the q-counter
           field so that .seqNumQMax is less than 2p–q.";
	    reference "IEEE1914 Table 5: seqNumQMax";
	  }

	  leaf q-counter {
	  type roe:sequence-id;
	  default 0;
	  description
	      "The counter value of the q-counter field. When
                   the q-counter > q-max, then the counter
                   field wraps to a value q-counter modulo
                   (q-max + 1).";
	  reference "IEEE1914 Table 5: seqNumQVal";
	  }

	  container q-increment {
	    reference "IEEE1914 Table 5: seqNumQIncProp";
	    leaf no-increment {
	      must "not(../fixed)";
	      type boolean;
	      description "No increment for the q-counter value";
	    }
	    leaf fixed {
	      type roe:sequence-id;
	      default 1;
	      must "not(../no-increment)";
	      description
	  	"Increment the q-counter by a fixed value on every
           p-counter wrap event.";
	      reference seqNumQInc;
	    }
	  }

      leaf subseq-rmax {
        type uint8;
        default 0;
        reference "subseqNumRMax";
        description "Maximum numerical value of the
                     r-counter subsequence field so that
                     subseq-rmax is less than 2^(q-rsubseq)";
      }
  
      leaf subseq-rval {
        type uint8;
        default 0;
        reference "subseqNumRVal";
        description "he counter value of the r-counter subsequence 
                     field.When the E-bit is set to logic 1, the 
                     .subseqNumRVal counter field wraps to 0 on the 
                     next packet. The E-bit can be set to logic 1 at 
                     any value of .subseqNumRVal. The E-bit must be set 
                     to logic 1 whenever the .subseqNumRVal counter field 
                     is equal to .subseqNumRMax.When the E-bit is set to 
                     logic 0, the .subseqNumRVal counter field increments 
                     by 1 on the next packet.";
        }
      
      leaf r-max {
        type roe:sequence-id;
        reference "IEEE19114 Table 5: seqNumRMax";
        default 0;
        description "Maximum numerical value of r-counter sequence field.
                     so that seqNumRMax < 2^(r_subseq-1-r_seq) if the 
                     r-subseq-counter and E bit are present and is 
                     < 2^(q-r_Seq) if the E bit and r-subsequence number
                     are not present";
        }

      leaf r-val {
        type uint8;
        default 0;
        reference "seqNumRVal";
        description "The counter value of the r-counter sequence field. 
                     When the .seqNumRVal > .seqNumRMax,then the counter 
                     field wraps to a value .seqNumRVal modulo (.seqNumRMax+1).";
        }
      
      container seq-num-rinc-prop {
        reference "seqNumRIncProp";
        leaf no-increment {
          type boolean;
          must "not(../fixed)";
          description "no increment";
        }
        leaf fixed {
          type uint8;
          must "not(../no-increment)";
          default 1;
          description "If the E-bit is present, increments by a fixed value indicated 
                       by seqNumRInc on the packet after a packet with its E-bit set 
                       to logic 1.";
        }
      }
     
	  leaf reserved-bits {
	    type uint32;
	    default 0;
	    description
                  "Static value for the optional reserved bits of the
                   sequence number field, when valid. Shall remain
                   unchanged for the lifetime of the flow.";
	    reference "IEEE1914 Table 5: seqNumRsvd";
        // Add must condition to validate ordertype to choose timestamp or seqnum
	  }
	}
  }

  /* Grouping for tiemstamp. This would be used when 
     orderInfo = timestamp
  */
  grouping timestamp {
    leaf timestamp {
      type uint32;
      description " Timestamp field provides the the start of framer 
      marker, a condensed sequence number and absolute time for 
      presentation of the packet information by the demapper at
      receiving point. It is represented in nanoseconds.
       ------------------------------------------------------------------------------------
      |start of frame (1)| seq num(2)| timestamp in ns (23)| fractional timestamp in ns (5)|
      ------------------------------------------------------------------------------------- ";
      reference "IEEE 1914.3 Section 5.5.5.3";
      }
    }

  /* Grouping for defining Mapper and demapper params
     Reference section Section 7.3.6 Table 10 & Table 11
  */
  grouping mapper-demapper {
   list mapper-demapper {
     key name;
     leaf name {
       type roe:mapper;
       description "Each RoE (de)mapper has a unique identifier";
       reference "mapperID";
     }
    /* function to identify mapper or a demapper since
       both are under the same group
    */
     leaf function {
        type enumeration {
          enum mapper {
            value 1;
            description "current id behaves as a mapper";
          }
          enum demapper {
            value 2;
            description "current id behaves as a demapper";
          }
        }
     }   
     leaf flow {
       type uint8; 
       reference "flowID";
       description " Assigned by the master controller to 
                     map to receiver's deMapperID.";
       default 0;
     }

     leaf source-link {
       type uint16;
       default 0;
       description "Identifies source ethernet link or CPRI port";
       reference "srcID";
     }

     leaf destination-ethernet-link {
       type uint16;
       default 0;
       description "Identifies destination Ethernet link";
       reference "destID";
      }

      leaf orderInfo {
        type enumeration {
          enum sequence-number {
            description "Sequence number is used";
            value 0;
          }
          enum time-stamp {
            description "Time stamp is used";
          }
        }
        reference "orderInfoType";
        //default sequence-number;
      }

      leaf roe-mapper-type {
        type enumeration {
          enum structure-agnostic-simple-tunneling {
            description "structure-agnostic-simple-tunneling mode";
            value 0;
          }
          enum structure-agnostic-no-enconding {
            description "structure-agnostic mode without line encoding";
            value 1;
          }
          enum structure-aware-time {
            description "structure aware time domain mode";
            value 2;
          }
          
          enum structure-aware-frequency {
            description "structure aware time domain mode";
            value 3;
          }
          enum native-time-domain {
            description "native time domain mode";
            value 4;
          }
          enum native-frequency-domain {
            description "native frequency domain mode";
            value 5;
          }
       }
       reference "mapperType";
     }

    /* The below leaf can be present for defining values in the future.
    */ 
    leaf enryption {
      description "Selects/enables encryption on a given flow.";
      default "none";
      type enumeration {
        enum none {
   	   description "No encryption";
          value 0;
   	   }
        }
      reference "encrypt";
    }

    // mappings associated with 16 compression and encryption schemes
    // Below leaf present for defining values in the future  
    leaf compression {
      description "Selects/enables compression on a given flow";
      default "none";
      type enumeration {
        enum none {
          description "No compression";
          value 0;
        }
      } 
      reference "compress";
    }

    leaf packet-length {
      description "Amount of data to include per packet payload";
      type uint16;
      default 0; // is default needed ? 
      reference "lenPack";
      units "octets for mapper-type 0,1,3,4 and container sets for mapper-type 2";
    }

    leaf accept-time-window {
      type uint32 {
        range "0..536870912"; // 29 bits
      }
      default 0;
      reference "acceptTimeWindow";
      description "Used along with OrderInfo timestamp and the arrival time of the 
                   timestamped radio data at de-mapper to determine if RoE packet
                   experienced excess trasit delay. use of the field is for 
                   error checking only.";
      }

      leaf sample-width {
        when "../roe-mapper-type != 'structure-agnostice'";
        type uint8;
        default 16;
        reference "sampleWidth";
        description "Indicates the number of bits in each I portion and in each Q
                     portion of an I/Q sample. By default 16 bit I and 16 bit Q is 
                     assumed.";
      }

      leaf num-containers {
        when "../roe-mapper-type = 'structure-aware-time' or ../roe-mapper-type = 'structure-aware-frequency'";
        type uint8;
        default 0;
        reference "numContainers";
        description "Defines the number of containers associated with this RoE
                     (de)mapper";
       }

       leaf num-control-containers {
         when "../roe-mapper-type = 'structure-aware-time' or ../roe-mapper-type = 'structure-aware-frequency'";
         type uint8;
         default 0;
         reference "numCtrlConts";
         description "Defines the number of control containers associated with 
                      this RoE (de)mapper.";
       }

       leaf num-fft {
         when "../roe-mapper-type = 'structure-aware-frequency' or ../roe-mapper-type = 'native-frequency-domain'";
         type uint8;
         reference "numFFT";
         default 0;
         description "Defines the number of (i)FFT objects";
       }

       leaf num-prach {
         when "../roe-mapper-type = 'structure-aware-frequency' or ../roe-mapper-type = 'native-frequency-domain'";
         type uint8;
         default 0;
         reference "numPRACH";
         description "Defines the number of PRACH objects";
       }

       leaf mapper-status-debounce {
         type uint8;
         default 1;
         reference "mapperStatDbnc";
         must "../function = 'demapper' and " +
              "(../roe-mapper-type = 'structure-agnostic' or " +
              " ../roe-mapper-type = 'structure-aware-frequency' or " +
              " ../roe-mapper-type = 'structure-aware-time')" {
           error-message "Function must be set to demapper and roe-mapper-type
                          to either structure-aware-time, structure-aware-frequency
                          or structure-agnostic";
         }
         description "Defines the debouncing required before each 
                      piece of information, individually, in a mapper 
                      status control packet is accepted. A value of 0 
                      means no debouncing of the value is used. The 
                      value in each packet will immediately be accepted. 
                      The default value of 1 means the value must be the 
                      same in two consecutive mapper status control packets 
                      before it is accepted.";
       }

       leaf loss-tod-rpl-pat {
         type uint8 {
            range "0..15"; //4 bits
         }
         default 0;
         must "../function = 'demapper'" {
           error-message "function must be set to demapper";
         }
         description " 0 PCS processed repeating all zeros
                       1 disabled transmitter
                       2 uncoded repeating all zeros
                       3 repeating PN-11 sequence ";
        }
       leaf cpri-dfct-rpl-patt {
         type uint8 {
           range "0..15"; //4 bits
         }
         default 0;
         must "../function = 'demapper'" {
            error-message "function must be set to demapper";
         }
         description " 0 PCS processed repeating all zeros
                       1 disabled transmitter
                       2 uncoded repeating all zeros
                       3 repeating PN-11 sequence ";
       }
       leaf buffer-udrun-rpl-patt {
         type uint8 {
           range "0..15"; //4 bits
         }
         default 4;
         must "../function = 'demapper'" {
            error-message "function must be set to demapper";
         }
         description " 0 PCS processed repeating all zeros
                       1 disabled transmitter
                       2 uncoded repeating all zeros
                       3 repeating PN-11 sequence ";
       }
       uses fft-definition;
       uses lowphy;
       uses prach-params;

       uses sequence-number {
         when "../orderInfo = 'sequence-number'";
       }
       uses timestamp {
         when "../orderInfo = 'timestamp'";
       }
       uses roe-container {
         when "../roe-mapper-type = 'structure-aware-time' or ../roe-mapper-type = 'structure-aware-frequency'";
       } 
       uses l3-qos-mapper-param {
            when "../function = 'mapper' and ../../encap-type = 'Ip'";
       }
     } 
     
     uses mapper-demapper;
  }
    
  /* L3 QOS params for ROE Mappers
  Section 7.3.6 Table 10
  */
  grouping l3-qos-mapper-param {
    leaf l3-pri-map0 {
      type uint8 {
        range "0..63"; //6 bits
      }
      default 0;
      reference "l3PriMap0";
      description "Defines the layer 3 (L3, i.e. IPv4 DSCP[5:0] 
                   or IPv6 Traffic Class[5:0]) priority level 
                   for RoE packets that have their layer 2 (L2) 
                   priority level set to 0.";
     }
 
    leaf l3-pri-map1 {
      type uint8 {
        range "0..63"; //6 bits
      }
      default 1;
      reference "l3PriMap1";
      description "Defines the layer 3 (L3, i.e. IPv4 DSCP[5:0] 
                   or IPv6 Traffic Class[5:0]) priority level 
                   for RoE packets that have their layer 2 (L2) 
                   priority level set to 0.";
     }
    leaf l3-pri-map2 {
      type uint8 {
        range "0..63"; //6 bits
      }
      default 2;
      reference "l3PriMap2";
      description "Defines the layer 3 (L3, i.e. IPv4 DSCP[5:0] 
                   or IPv6 Traffic Class[5:0]) priority level 
                   for RoE packets that have their layer 2 (L2) 
                   priority level set to 0.";
     }
    leaf l3-pri-map3 {
      type uint8 {
        range "0..63"; //6 bits
      }
      default 3;
      reference "l3PriMap3";
      description "Defines the layer 3 (L3, i.e. IPv4 DSCP[5:0] 
                   or IPv6 Traffic Class[5:0]) priority level 
                   for RoE packets that have their layer 2 (L2) 
                   priority level set to 0.";
     }
    leaf l3-pri-map4 {
      type uint8 {
        range "0..63"; //6 bits
      }
      default 4;
      reference "l3PriMap4";
      description "Defines the layer 3 (L3, i.e. IPv4 DSCP[5:0] 
                   or IPv6 Traffic Class[5:0]) priority level 
                   for RoE packets that have their layer 2 (L2) 
                   priority level set to 0.";
     }
    leaf l3-pri-map5 {
      type uint8 {
        range "0..63"; //6 bits
      }
      default 5;
      reference "l3PriMap5";
      description "Defines the layer 3 (L3, i.e. IPv4 DSCP[5:0] 
                   or IPv6 Traffic Class[5:0]) priority level 
                   for RoE packets that have their layer 2 (L2) 
                   priority level set to 0.";
     }
    leaf l3-pri-map6 {
      type uint8 {
        range "0..63"; //6 bits
      }
      default 6;
      reference "l3PriMap6";
      description "Defines the layer 3 (L3, i.e. IPv4 DSCP[5:0] 
                   or IPv6 Traffic Class[5:0]) priority level 
                   for RoE packets that have their layer 2 (L2) 
                   priority level set to 0.";
     }
    leaf l3-pri-map7 {
      type uint8 {
        range "0..63"; //6 bits
      }
      default 7;
      reference "l3PriMap7";
      description "Defines the layer 3 (L3, i.e. IPv4 DSCP[5:0] 
                   or IPv6 Traffic Class[5:0]) priority level 
                   for RoE packets that have their layer 2 (L2) 
                   priority level set to 0.";
     }
  }

  /* Ethernet Header details
  */
  grouping encapsulation {
    leaf destination-address {
      description "The destination MAC address in the ethernet encapsulation";
      type ietf-yang-types:mac-address; 
    }

    leaf source-address {
      description "The source MAC address in the ethernet encapsulation";
      type ietf-yang-types:mac-address;
    }

    leaf vlanid {
      description "Vlan ID part of the Ethernet header";
      type uint32 {
        range "0..4096";
      }
    }

    leaf source-ip {
      description "SourceIP of the packet";
      type ietf-inet-types:ip-address;
      must "../encap-type = 'Ipheader'" {
        error-message "Encapsulation should be IP Header";
       }
     }

    leaf destination-ip {
      description "Destination IP of the packet";
      type ietf-inet-types:ip-address;
      must "../encap-type = 'Ipheader'" {
        error-message "Encapsulation should be IP Header";
      }
    }

    leaf source-udp-port {
      description "Source UDP port";
      type ietf-inet-types:port-number;
      must "../encap-type = 'Ipheader'" {
        error-message "Encapsulation should be IP Header";
      }
    }

    leaf destination-udp-port {
      description "Destination UDP port";
      type ietf-inet-types:port-number;
      must "../encap-type = 'Ipheader'" {
        error-message "Encapsulation should be IP Header";
      }
    }

    leaf encap-type {
      type enumeration {
        enum "Ethernet" {
          value 0;
          description "Ethernet only header";
        }
        enum "Ip" {
          value 1;
          description "Optional IP header";
         }
       }
     }
   }  


  /* RoE container params as per 
     section 8.3.1 and Table 13
  */
  grouping roe-container {
    container roe-container {
      list id {
        key name;
        leaf name {
          type string;
          description "Name of the roe-container";
        }
        leaf mapper-demapper-id {
          type roe:mapper;
          description "(de)mapper ID to which this container belongs.
                       containers that do not belong to specific 
                       (de)mapperID but processed separately like CPRI
                       control words, shall set the value to ALL_ONES 
                       flowID.";
        }
        leaf len-skip {
          type uint8;
          description " The number of reserved bit in front of the 
                        extracted container.";
        }
        leaf len-container {
          type uint16 {
            range "0..1024"; // 10 bits 
          }
          description "Size of the container in bits";
        }
        leaf modulo {
          type uint16 {
            range "0..256"; // 9 bits
          }
          description "Value from 0-256. value 0 turns off the
                       modulo logic";
        }
        leaf index {
          type uint8;
          // index not used when modulo = 0
          must "not(../modulo = 0)";
          description "Index to match after the modulo operation. Valid values
                       from 0 to modulo-1";
          }
        //container roe-header {
        //  uses roe-header;
        //}
      }
    }
  }


  /* CPRI control word RoE mapper
     Section 8.3.9 Table 15
  */
  grouping cpri-ctrl-roe-mapper {
    list ctrl-word {
      key name;
      leaf name {
        type string;
        description "Name of the control word mapper";
      }
      leaf ctrl-word-id {
        type uint8;
        description "Unique identifier for each control word";
      }
      leaf flow-id {
        type uint8;
        description "FlowId used in control process container
                     construction for generated RoE packets.
                     The flow-id = ctrl-word-id ";
      }
      leaf cw-sel {
      /* was changed to 4 bits from 3 based on discussion 
         during the bi-weekly meeting held on 03-17-2020
      */
        type uint8 {
          range "0..15"; //4 bits
        }
        description "A 4 bit mask for selecting subchannel 
                     words to extract. Bit 0 corresponds to
                     Xs words with index 0 and bit 3 corres
                     -ponds to Xs=3. The selected subchannel
                     are equal to logical OR of the correspo
                     -nding subchannel masks.";
      }
      leaf cw-start {
        type uint8 {
          range "0..63"; // six bits
        }
        description "The first subchannel allocated for parser";
      }
      leaf cw-size {
        type uint8 {
          range "0..63"; // Six bits
        }
        description "Number of consecutive subchannels allocated
                     for control data.";
      }
      leaf filter-mode {
        type uint8 {
          range "0..8";
        }
        description "Controls the generation of RoE packets
                      from extracted CPRI control words.";
      }
      leaf hfn-modulo {
        type uint8 {
          range "1..150";
        }
        must "boolean(../filter-mode)" {
          error-message "filter-mode configuration missing";
        }
        description "Modulo operation applied to current CPRI
                     hyper frame number. Whether the modulo is 
                     applied depends on filter-mode setting.";
      }
      leaf cw-offset {
        type uint16 {
          range "0..4095";// 12 bits
        }
        must "boolean(../filter-mode)" {
          error-message "filter-mode configuration missing";
        }
        description "The offset into the extracted control word
                     buffer for masking and value comparison 
                     operation."; 
      } 
      leaf cw-value {
        type uint32;
        description "The value against which to compare after 
                     mask operation";
      }
      leaf cw-mask {
        type uint32;
        description "The bit mask (logical AND) for the offset
                     based comparison operation";
      }
    }
  }
     

  /* Grouping for PRACH. Physical random access channel is used to 
     obtain synchronization between UE and eNB. This function is 
     relevant only in the uplink direction.
     Reference Section 8.5.5 Table 19
  */
  grouping prach-params {
    leaf prach-id {
      type uint8;
      description "Each PRACH in each mode has a unique ID";
      default 0;
    }
    leaf prach-config-index {
      type uint8;
      default 0;
      description "The PRACH configuration index, which sets the preamble 
                   format and system frame number and the sub frame number
                   positions of the PRACH in time in radio frames.";
    }
    leaf prach-offset {
      type uint16;
      default 0;
      description "Sets the PRACH position in frequency/subcarrier
                   position and is expressed as a physical resource
                   block number. Set by S1B2, prach-freqOffset in 
                   E-UTRA.";
     }
     leaf prach-sample-width {
       type uint8;
       default 16;
       description "Indicates the total number of bits in each I/Q 
                    sample in bits. By default 16 bit I and 16 bit
                    Q width is assumed.";
     }
  }
  

  /* Native RoE frequency domain packet mapper 
     Section 8.5 Table 18
  */
  grouping fft-definition {
    leaf fft-id {
      type uint8;
      default 0;
      description "Unique identifier for each (i)FFT";
    }

    leaf rb-fft {
      type uint16;
      default 100;
      description "The number of resource blocks on which the (i)FFT
                   operates";
    }

    leaf fft-size {
      type uint16;
      default 2048;
      description "The size in bins for the (i)FFT";
    }

    leaf cp-len-zero {
      type uint16;
      default 160;
      description "Identifies the cyclic prefix length when l=0.
                   symbols are transmitted in the increasing 
                   order of l, starting with l=0";
    }

    leaf cp-len-other {
      type uint16;
      default 144;
      description "Identifies the cyclic prefix length N for 
                   symbols when l > 0. symbols are transmitted 
                   in increasing order of l, starting with l=0.";
    }

    leaf map-rb {
      type uint8;
      default 0;
      description "The number of bits per rb-fft to be allocated
                   to the rb-map field of the RoE native frequency
                   domain subtype. when map-rb = 0 , rb-map field 
                   if zero size. All resource blocks are contained 
                   in packet.";
    }

    leaf allow-rb {
      type uint16;
      default 100;
      must "../map-rb != 0" {
        error-message "allow-rb valid only when map-rb is not equal to 0";
      }
      description "A 1 in the .allowRB indexed bit indicates 
                   the indexed resource block can be carried 
                   in the flow’s packets.
                   A 0 in the .allowRB indexed bit indicates 
                   the indexed resource block is not carried 
                   in the flowID’s packets (i.e. it could be 
                   carried in another flowID’s packets).";
     }
  }

  /* Grouping lowPHY branch 
     Reference Table 19a 
  */
  grouping lowphy {
    leaf bandwidth {
      type uint8;
      default 5;
    }
    
    leaf sample-freq {
      type uint8;
      default 5;
    }

    leaf sc-spacing {
      type uint8;
      default 0;
    }

    leaf fd-sample-width {
      type uint8;
      default 16;
    }

    leaf fd-iq-format {
      type uint8;
      default 0;
    }

    leaf fd-iq-mansize {
      type uint8;
      default 13;
    }

    leaf fd-iq-expsize {
      type uint8 {
        range "0..127"; //7 bits
      }
      default 3;
    }
   
    leaf fd-iq-endian {
      type boolean;
      default false;
    }

    leaf cpri-iq-format {
      type uint8;
      default 0;
    }

    leaf cpri-iq-mansize {
      type uint8;
      default 13;
    }

    leaf cpri-iq-exp-size {
      type uint8;
      default 13;
    }

    leaf cpri-iq-endian {
      type boolean;
      default false;
    }
  }

  /* Starting toplevel CPRI container
  */
  grouping cpri { 
    container cpri {
     list port {
      description "List of CPRI ports";
      key name;
      leaf name {
        type roe:cpri-id;
        description "CPRI-ID for the port";
        reference "cpriID";
      }
      leaf version {
        type uint8;
        reference "cpriVer";
        default 0;
        description " Protocol version at location Z.2.0
                      i.e. control word 2.";
       }
      leaf speed {
        type roe:speed;
        description "Port speed in Mbps";
        default 0;
        reference "cpriSpeed";
      }
      leaf hdlc-rate {
        description " HDLC bit rate at location Z.66.0, 
                      i.e. control word 66.";
        type uint8 {
          range "0..7"; // three bits
        }
        reference "cpriHDLC";
      }
      leaf l1-location {
        description "L1 signalling at location Z.130.0,
                     i.e. control word 130.";
        type uint8 {
          range "0..31"; //Five bits
        }
        default 0;
        reference "cpriL1";
      }
      leaf ethernet-pointer {
        type uint8 {
          range "0..63"; // Six bits
        }
        reference "cpriEth";
       }
      leaf scramble-speed {
        description "The 31-bit seed used to descramble the incoming 
                    CPRI stream to the RoE mapper or to scramble the 
                    outgoing CPRI stream at the RoE de-mapper. This 
                    seed corresponds to the scrambling seed bits, c30, 
                    c29, ... c1, c0. from the CPRI specification.";
        type uint32 {
          range "0..2147483648"; // 2^31
        }
        reference "cpriScrSeed";
        default 0;
      }
      leaf fec-mode {
        description "The CPRI forward error correcton (FEC) mode on 
                     the incoming CPRI stream to the RoE mapper or 
                     on the outgoing CPRI stream at the RoE de- mapper.
                     0 RS_FEC disabled mode
                     1 RS FEC enabled mode. ";
        type uint8;
        reference "cpriFecMode";
        default  0;
      }
     }
   }
  }
 

  /* main block calling respective groups
  */ 
  uses encapsulation;
  uses cpri;
}
